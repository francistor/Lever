// Contents of "files-example.yang"
module files-example {
    namespace "http://indra.es/irestconf/files-example";
    prefix "files-example.irestconf.indra.es";
    
    organization "Indra Sistemas S.A.";
    contact "frodriguezg@indra.es";
    
    description
        "Example mapping from configuration files to YANG";
    
    revision 2016-02-29 {
        description "Initial revision.";
    }
    
    container plain-properties {
    	description
    		"plain.properties file";
    	
        leaf property1 {
            type string;
            description "Example property 1";
        }
        
        leaf property2 {
            type string;
            description "Example property 2";
        }
    }
    
    container plain-section-properties {
    	
    	description 
        	"plain.section.properties file";
    	
    	container section1{
    		
    		description
    			"section 1 contents";
    		
    		leaf property1 {
                type string;
                description "Example property 1";
            }
            
            leaf property2 {
                type string;
                description "Example property 2";
            }
    	}
    }
}
